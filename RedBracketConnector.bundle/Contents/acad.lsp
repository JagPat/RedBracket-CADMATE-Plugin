(SETQ  ACADLSPASDOC  0)
NETLOAD "C:\\Program Files\\Autodesk\\ApplicationPlugins\\RedBracketConnector.bundle\\Contents\\RBAutocadPlugIn.dll")
(Command "_Ribbon")
(Command "COMMANDLINE")
(Command "NETLOAD" "C:\\Program Files\\Autodesk\\ApplicationPlugins\\RedBracketConnector.bundle\\Contents\\RBAutocadPlugIn.dll")
(Command "RBRIBBON")
